;;;************VẼ CẦU THANG*************************
(defun c:vct( / p c r sb oldos)  (setq    p (getpoint "\nChọn điểm đầu tiên:")    c (getdist p "\nNhập chiều cao của bậc:")    r (getdist p "\nNhập chiều rộng của bậc:")    sb (getint "\nNhập số bậc:")    oldos (getvar "osmode")  )  (setvar "osmode" 0)    (command ".pline")  (command p)    (repeat sb    (command (strcat "@0," (rtos c)))    (command (strcat "@" (rtos r) ",0"))  )  (command "")  (setvar "osmode" oldos)  (princ))
