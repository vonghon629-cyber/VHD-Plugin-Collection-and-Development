;;;************ÐÃòT TIÒ LÊò VIEWPORT TRONG LAYOUT*************************
(defun c:TL (/ zxp)
(if (setq zxp (getreal "Nhâòp tiÒ lêò Viewport: 1/..."))
(command "zoom" (strcat "1/" (rtos zxp 2 0) "xp")))
(princ))
