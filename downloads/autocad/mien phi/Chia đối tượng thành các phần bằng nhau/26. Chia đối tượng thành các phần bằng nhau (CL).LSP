;;;************CHIA ĐỐI TƯỢNG THÀNH CÁC PHẦN BẰNG NHAU*************************
(defun c:CL(/ e ename p1 p2 x1 y1 x2 y2 sk i )
(setq e (entget(setq ename (car(entsel "\nChọn đoạn thẳng cần chia:"))))		
		x1 (car (setq p1 (getpoint "\nChọn điểm đầu:")))
		y1 (cadr p1)
		x2 (car (setq p2 (getpoint p1 "\nChọn điểm cuối:")))
		y2 (cadr p2)
		sk (getint "\nSố khoảng cần chia:")
		i 0
)
(command "_Pline")
(command (cdr (assoc '10 e)))
(repeat (+ 1 sk)
	(command (setq points 
	(list (+ x1 (* i (/ (- x2 x1) sk)))
		  (+ y1 (* i (/ (- y2 y1) sk)))
			0)))
		(setq i (1+ i))
		)
(command (cdr (assoc '11 e)) "")
(entdel ename)		
)
