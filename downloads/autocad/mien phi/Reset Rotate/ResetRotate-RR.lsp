(defun c:RR (/ ang ss name)
  (vl-load-com)
  (setq ang (atan (cadr (trans (getvar 'UCSXDIR) 0 (trans '(0. 0. 1.) 1 0 T) T)) (car (trans (getvar 'UCSXDIR) 0 (trans '(0. 0. 1.) 1 0 T) T))))
  (if (ssget "_:L" '((0 . "INSERT,MTEXT,MULTILEADER,TEXT")))
    (progn
      (vlax-for x (vla-get-activeselectionset (vla-get-activedocument (vlax-get-acad-object)))
        (cond ((vl-position (setq name (vla-get-objectname x)) '("AcDbBlockReference" "AcDbText")) (vla-put-rotation x ang))
              ((eq name "AcDbMText") (vla-put-rotation x 0.))
              ((and (eq name "AcDbMLeader") (eq (vla-get-contenttype x) 2)) (vla-put-textrotation x 0.))))
      (vla-delete ss)
    )
  )
  (princ)
)
