;;;************VẼ ĐƯỜNG HÀN*************************
(defun c:HX ()
(setq om (getvar "osmode"))
(setq p1 (getpoint "\nChọn điểm đầu:"))
(setq p2 (getpoint p1 "\nChọn điểm cuối:"))
(setq hstl 10)
(command "osnap" "none")
(setq a (angle p1 p2))
(setq l (distance p1 p2))
(setq n (fix (/ l hstl)))
(setq p3 (polar p1 a (/ (- l (* n hstl)) 2)) )
(repeat (+ n 1)
(progn (setq p4 (polar p3 (+ a (/ pi 2)) hstl))
(command "line" p3 p4 "")
(setq p3 (polar p3 a hstl))
)
)
(setvar "osmode" om)
)

(defun c:HH ()
(setq om (getvar "osmode"))
(setq p1 (getpoint "\nChọn điểm đầu:"))
(setq p2 (getpoint p1 "\nChọn điểm cuối:"))
(setq hstl 10)
(command "osnap" "none")
(setq a (angle p1 p2))
(setq l (distance p1 p2))
(setq n (fix (/ l hstl 1.5)))
(setq p3 (polar p1 a (+ (/ (- l (* n hstl 1.5)) 2) (* 0.25 hstl)) ) )
(setq p4 (polar p3 (+ a (/ pi 2)) hstl))
(repeat n
(progn (setq p5 (polar p3 a hstl))
(setq p6 (polar p5 (+ a (/ pi 2)) hstl))
(command "line" p3 p6 "")
(command "line" p4 p5 "")
(setq p3 (polar p3 a (* 1.5 hstl)))
(setq p4 (polar p4 a (* 1.5 hstl)))

)
)
(setvar "osmode" om)
)
