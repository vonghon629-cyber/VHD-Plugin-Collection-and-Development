;;;************CÃìT CHÂN DIM CAìCH 1 ÐÝÕÌNG THÃÒNG COì GIAì TRIò CHO TRÝÕìC*************************
(defun c:KN(/ CAOC G1 G2 LI SS TT10 TT13 TT14 TT9)
(defun dxf(id v) (cdr (assoc id (entget v))))
(defun doi (id tri v) (entmod (subst (cons id tri) (assoc id (entget v)) (entget v)))) 
(defun dxf9(v / tt10 tt13 tt14 tt50 tt9)
 (setq tt10 (dxf 10 v)
tt13 (dxf 13 v)
tt14 (dxf 14 v)
tt50 (dxf 50 v) 
  tt9 (inters tt10 (polar tt10 tt50 1) tt13 (polar tt13 (angle tt14 tt10) 1) nil)     
 )
)
;;;
(princ "\n Choòn Dim:")  (setq ss (ssget '((0 . "DIMENSION"))))
(princ "\n Choòn Line:") (setq li (ssname (ssget ":S:E" '((0 . "LINE") )) 0))
(setq caoc (getreal (strcat "\n Caìch khoaÒng: <" (if gl_caoc (rtos gl_caoc) (rtos (setq gl_caoc 500))) ">")))
(if caoc (setq gl_caoc caoc))
 
  (foreach obj (vl-remove-if 'listp (mapcar 'cadr (ssnamex ss)))
      (setq  tt13 (dxf 13 obj)
    tt14 (dxf 14 obj)
    tt10 (dxf 10 obj)
    tt9 (dxf9 obj)
g1 (inters (dxf 10 li) (dxf 11 li) tt10 tt14 nil)
g2 (inters (dxf 10 li) (dxf 11 li) tt9 tt13 nil)
)
   (if g1 (doi 14 (polar g1 (angle g1 tt10) gl_caoc) obj))
   (if g2 (doi 13 (polar g2 (angle g2 tt9) gl_caoc) obj))
  )
)
