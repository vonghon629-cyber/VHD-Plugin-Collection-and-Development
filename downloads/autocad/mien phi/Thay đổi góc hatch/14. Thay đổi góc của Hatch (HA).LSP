;;;************THAY ĐỔI GÓC CỦA HATCH*************************
(defun c:HA	()
(setq ename(entsel "\nLựa chọn mẫu Hatch để thay đổi góc!")
elist(entget (car ename))
etyp(cdr (assoc 0 elist))
oang(assoc 52 elist)
);setq

(if (/= etyp "HATCH")
(prompt "\nKhông phải đối tượng Hatch! Hãy thử lại!")
(progn
(setq ang (getangle (strcat "\nSố đo góc mới: <" (rtos (cdr oang) 2) ">"))
nang (cons 52 ang)
nlst (subst nang oang elist)
)
(entmod nlst)
(command "hatchedit" ename "" "" "" "")
);progn
);if
(princ)
);defun
