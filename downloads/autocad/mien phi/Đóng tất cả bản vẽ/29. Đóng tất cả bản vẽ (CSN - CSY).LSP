;;;************ÐOìNG TÂìT CAÒ BAÒN VEÞ*************************
(vl-load-com)
(defun C:CSN ( / dwg)
 (vlax-for dwg (vla-get-Documents (vlax-get-acad-object))
  (if (= (vla-get-active dwg) :vlax-false)(vla-close dwg :vlax-false))
 )
 (command "._close" "_y")
)
(defun C:CSY ( / dwg)
 (vlax-for dwg (vla-get-Documents (vlax-get-acad-object))
  (if (= (vla-get-active dwg) :vlax-false)(vla-close dwg :vlax-true))
 )
 (command "._close" "_n")
)
