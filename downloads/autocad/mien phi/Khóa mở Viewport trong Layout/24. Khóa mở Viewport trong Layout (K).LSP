;;;************KHÓA MỞ VIEWPORT TRONG LAYOUT*************************
(defun C:K ( / SelSet ST:VP-Toggle-DisplayLocked) ;VP toggle Locked
;======== Local Function =========
(defun ST:VP-Toggle-DisplayLocked (vpObj / rt)
;vp : vlaObject
;RT : T if Lock VP / nil if Open
(cond ((eq (vla-get-DisplayLocked vpObj) :vlax-false)(vla-put-DisplayLocked vpObj :vlax-true)(setq rt T)(vla-put-color vpObj acMagenta))
		(T (vla-put-DisplayLocked vpObj :vlax-False)(vla-put-color vpObj acByLayer)))
)
;========== Start Here ==============
(grtext -1 "Khóa hoặc mở khóa Viewport trong Layout!")
 (cond
  ((< (atof (getvar "ACADVER")) 15.0)
   (alert " Lisp yêu cầu từ AutoCAD 2000 hoặc cao hơn!")
  )
  ((or (= (getvar "TILEMODE") 1) (> (getvar "CVPORT") 1))
   (alert "Lisp chỉ có thể được thực hiện trong không gian giấy!")
  )
  ((and
    (not (prompt "\nChọn Viewport để mở hoặc khóa!"))
    (not (setq SelSet (ssget '((0 . "VIEWPORT")))))
   )
   (princ "Đối tượng bạn chọn không phải Viewport!")
  )
  (T
   (vl-load-com)
   (vlax-for vpObj (setq SelSet (vla-get-ActiveSelectionSet (vla-get-ActiveDocument (vlax-get-acad-object))))
	 (ST:VP-Toggle-DisplayLocked vpObj)	 
    )
	)
 )
 (princ)
)
