;;;************OFFSET ĐỐI TƯỢNG SANG HAI BÊN VỚI 1 KHOẢNG CÁCH CHO TRƯỚC*************************
(defun c:46 (/ ss objlst dist entlst1 entlst2 kwrd)
(or #dist(setq #dist 220))
(setq dist (getdist (strcat "\nNhập khoảng cách cần Offset: <"(rtos #dist 2 0)">")))
(if dist (setq #dist dist))
(princ "\nChọn đối tượng cần Offset:")
(setq ss (ssget '((0 . "LWPOLYLINE,LINE,ARC,CIRCLE,ELLIPSE,SPLINE"))))
(if ss
(progn
(setq objlst (mapcar 'vlax-ename->vla-object(vl-remove-if 'listp (mapcar 'cadr (ssnamex ss)))))
(initget (+ 2 4) "C K")
(setq kwrd  (getkword "\nBạn có muốn xóa đối tượng gốc không? [Có/Không]:"))
(if (null kwrd)
(setq kwrd "K")
)
(foreach obj objlst
(vla-offset obj #dist)
(setq entlst1 (cons (vlax-ename->vla-object (entlast)) entlst1)) 
(vla-offset obj (* #dist -1))
(setq entlst2 (cons (vlax-ename->vla-object (entlast)) entlst2))
(mapcar '(lambda (x) (vla-put-layer x (getvar "clayer"))) entlst1)
(mapcar '(lambda (x) (vla-put-layer x (getvar "clayer"))) entlst2)
(if (eq kwrd "C")
(vla-erase obj)
)
)
)
)
(princ)
)
