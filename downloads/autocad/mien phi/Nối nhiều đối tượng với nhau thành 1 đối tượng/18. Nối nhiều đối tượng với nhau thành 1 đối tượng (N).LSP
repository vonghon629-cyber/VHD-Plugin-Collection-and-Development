;;;************NÔìI NHIÊÌU ÐÔìI TÝÕòNG VÕìI NHAU THAÌNH 1 ÐÔìI TÝÕòNG*************************
(defun c:N (/ tdt ssdt)
  (defun ObjName (ssdt /)  (cdr (assoc '0 (entget ssdt))))
  (defun MoPL (ssdt /) (= (cdr (assoc '70 (entget ssdt))) 0))
  
  (defun NoiPL (ssdt tdt /)
    (if (MoPL ssdt)
      (command ".PEDIT" ssdt "J" tdt "" "")
    )
  )
  (defun NoiLC (ssdt tdt /)  (command ".PEDIT" ssdt "Y" "J" tdt "" ""))
  
  (setq tdt  (ssget)
ssdt  (ssname tdt 0))
  (if (or (= (Objname ssdt) "LWPOLYLINE")
 (= (Objname ssdt) "POLYLINE"))
    (NoiPL ssdt tdt)
    (if (or (= (Objname ssdt) "LINE") (= (Objname ssdt) "ARC"))
      (NoiLC ssdt tdt)
    )
  )
  (princ)
)
