;;;************VEÞ TÝÕÌNG BAO TÝÌ TIM HOÃòC TRUòC*************************
(defun C:VTT(/ lstd lstn lstg1 lstg x y)
 (vl-load-com)
 (command "undo" "be")
 (princ "\nChoòn caìc ðôìi týõòng <Tim> hoãòc <Truòc>")
 (foreach ent (vl-remove-if 'listp (mapcar 'cadr (ssnamex (ssget '((0 . "LINE"))))))
  (if (equal (car (cdr (assoc 10 (entget ent)))) (car (cdr (assoc 11 (entget ent)))) 1E-8)
   (setq lstd (cons ent lstd))
   (setq lstn (cons ent lstn))))
 (setq lstd (vl-sort lstd '(lambda (e1 e2) (< (car (cdr (assoc 10 (entget e1)))) (car (cdr (assoc 10 (entget e2))))))))
 (setq lstn (vl-sort lstn '(lambda (e1 e2) (< (cadr (cdr (assoc 10 (entget e1)))) (cadr (cdr (assoc 10 (entget e2))))))))
 (or kc (setq kc 110))
 (setq kc (cond ((getdist (strcat "\nNhâòp chiêÌu daÌy cuÒa týõÌng: <"(rtos kc 2 0)">"))) (kc)))
 (foreach entn lstn
  (setq lstg1 nil)
  (foreach entd lstd
   (if (setq giao (car (HA:Giao (vlax-ename->vla-object entn) (vlax-ename->vla-object entd) acExtendNone)))
    (setq lstg1 (cons giao lstg1))))
  (if lstg1 (setq lstg (cons lstg1 lstg))))
 (HA1 (caar lstg) (last (last lstg)) kc)
 (setq x 0)
 (repeat (1- (length lstg))
  (setq y 0)
  (repeat (1- (length (nth x lstg)))
   (HA (nth y (nth (1+ x) lstg)) (nth (1+ y) (nth x lstg)) kc)
   (setq y (1+ y)))
  (setq x (1+ x)))
 (command "undo" "e") 
 (princ))
(defun HA:Giao(obj1 obj2 mode / l r)
 (setq l (vlax-invoke obj1 'intersectwith obj2 mode))
 (repeat (/ (length l) 3)
  (setq r (cons (list (car l) (cadr l) (caddr l)) r) l (cdddr l)))
 r)
(defun HA(p1 p3 kc / p1x p3x)
 (setq p1x (list (+ (min (car p1) (car p3)) kc) (+ (min (cadr p1) (cadr p3)) kc))
       p3x (list (- (max (car p1) (car p3)) kc) (- (max (cadr p1) (cadr p3)) kc)))
 (command "rectang" "non" p1x "non" p3x))
(defun HA1(p1 p3 kc / p1x p3x)
 (setq p1x (list (- (min (car p1) (car p3)) kc) (- (min (cadr p1) (cadr p3)) kc))
       p3x (list (+ (max (car p1) (car p3)) kc) (+ (max (cadr p1) (cadr p3)) kc)))
 (command "rectang" "non" p1x "non" p3x))
