;;;************BREAK ĐỐI TƯỢNG*************************
(defun c:BF (/ dt diem)  (setq	dt   (car (entsel "\nChọn đối tượng cần chặt")))  (if dt    (progn      (redraw dt 3)        (setq diem (getpoint "\nChọn điểm chặt: "))      (redraw dt 4)    )  )    (if (and dt diem)        (command ".break" dt diem diem)  )  )
