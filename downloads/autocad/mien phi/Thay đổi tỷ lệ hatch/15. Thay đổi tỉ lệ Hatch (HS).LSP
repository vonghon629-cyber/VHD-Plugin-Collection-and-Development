;;;************THAY ĐỔI TỈ LỆ MẪU HATCH*************************
(defun c:HS	()
(setq ename	(entsel "\nLựa chọn mẫu Hatch để thay đổi tỷ lệ:")
elist (entget (car ename))
etyp	(cdr (assoc 0 elist))
oscl (assoc 41 elist)
);setq

(if (/= etyp "HATCH")
(prompt "\nKhông phải đối tượng Hatch! Hãy thử lại!")
(progn
(setq hscl (getreal (strcat "\nTỷ lệ mẫu Hatch mới: <" (rtos (cdr oscl) 2) ">"))
nscl (cons 41 hscl)
nlst (subst nscl oscl elist)
)
(entmod nlst)
(command "hatchedit" ename "" "" "" "")
);progn
);if
(princ)
);defun
