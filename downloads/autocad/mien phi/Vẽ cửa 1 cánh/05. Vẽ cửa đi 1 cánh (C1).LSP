;;;************VẼ CỬA ĐI 1 CÁNH*************************
(defun C:C1 (/ p1 p2 p3 p4 side dis wid ang angsile old)
 (setq old (getvar "OSMODE")) 
 (setvar "OSMODE" 171)
(command "osnap"  "")
(command "osnap" "End,Mid,Cen,Quad,Int,Perp,Tan,Near,App,Int,Ext,Par"  )
 (setq p1 (getpoint "\nChọn điểm đầu:"))
 (setq p2 (getpoint p1 "\nChọn điểm tiếp theo:"))
 (setq side (getpoint p2 "\nChọn hướng mở cửa:"))
 (setq dis (distance p1 p2))
 (setq ang (angle p1 p2))
 (if (< ang (angle p1 side))
  (setq angside    (/ pi 2) )
  (setq angside (- (/ pi 2))) )
 (if  (>= (- (angle p1 side) ang) pi)
  (setq angside (- (/ pi 2))) )
 (if  (>= (- ANG (angle p1 side) ) pi)
  (setq angside (/ pi 2)) )
 (setq p3 (polar p2 (+ ang angside) dis) )
 (setq p4 (polar p1 (+ ang angside) dis) )
 (setq wid (/ dis 15))
 (setvar "OSMODE" 0)
(command "layer" "m" "0" "c" "white" """")
 (command "PLINE" p1 "A" "D" p4 "0.13" p3 "L" p2 
                  (polar p2 (+ ang pi) wid) 
                  (polar p3 (+ ang pi) wid)  "")
(setvar "OSMODE" old)
(command "osnap"  "")
(command "osnap" "End,Mid,Cen,Quad,Int,Perp,Tan,Near,App,Int,Ext,Par"  )
 (princ))
