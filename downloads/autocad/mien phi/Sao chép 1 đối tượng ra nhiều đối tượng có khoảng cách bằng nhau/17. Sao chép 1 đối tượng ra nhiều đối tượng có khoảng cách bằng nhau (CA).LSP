;;;************SAO CHÉP ĐỐI TƯỢNG RA NHIỀU ĐỐI TƯỢNG CÓ KHOẢNG CÁCH BẰNG NHAU*************************
(defun C:CA (/ dt p1 p2 sl x)
(command "undo" "be")
(setq osm (getvar "osmode"))
(setq dt (ssget)
     	p1 (getpoint "\nChọn điểm đầu:")
     	p2	(getpoint p1 "\nNhập khoảng cách:")
     	sl 	(getint "\nSố đối tượng cần sao chép:")
     	x 1)
(setvar "osmode" 0)
(repeat sl
 (command "copy" dt "" p1 (polar p1 (angle p1 p2) (* (distance p1 p2) x)))
 (setq x (1+ x)))
(command "undo" "e")
(setvar "osmode" osm)
(princ))
